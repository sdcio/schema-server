module dummy {
    yang-version 1.1;
    namespace "urn:dummy/dummy";
    prefix "dummy_dummy";
    container foo {
        list bar {
            key "k2 k1"; // unsorted keys
            leaf k1 {
                type string;
            }
            leaf k2 {
                type string;
            }
            leaf attr1 {
                type string;
            }
            container subbar {
                leaf subattr1 {
                    type string;
                }
            }
            // choice under list with implicit cases
            choice choix1 {
                leaf ch11 {
                    type string;
                }
                leaf ch12 {
                    type string;
                }
            }
            // choice under list with explicit cases
            choice choix2 {
                case cas1 {
                    leaf ch21 {
                        type string;
                    }
                }
                case cas2 {
                    leaf ch22 {
                        type string;
                    }
                }
            }
        }
        container foo1 {
            // choice with implicit cases
            choice c1 {
                container case1-container {
                    leaf cas1_leaf {
                        type string;
                    }
                }
                container case2-container {
                    leaf cas2_leaf {
                        type string;
                    }
                }
                leaf cas3-leaf {
                    type string;
                }
            }
        }
        list unique-one {
            key "id";
            unique "ip port";
            leaf id {
                type string;
            }
            leaf ip {
                type string;
            }
            leaf port {
                type uint16;
            }
        }
        list no-unique {
            key "id";
            leaf id {
                type string;
            }
            leaf val {
                type string;
            }
        }
        list unique-two {
            key "id";
            unique "ip port";
            unique "name";
            leaf id {
                type string;
            }
            leaf ip {
                type string;
            }
            leaf port {
                type uint16;
            }
            leaf name {
                type string;
            }
        }
        container foo2 {
            // choice with explicit cases
            choice c2 {
                case cas1 {
                    container c2-1 {
                        leaf leaf-c2-1 {
                            type string;
                        }
                    }
                }
                case cas2 {
                    container c2-2 {
                        leaf leaf-c2-2 {
                            type string;
                        }
                    }
                }
            }
            container c3-1 {
                leaf l1 {
                    type string;
                }
            }
        }
    }
}
